module messenger {
    yang-version 1;
    namespace "urn:opendaylight:params:xml:ns:yang:messenger";
    prefix "messenger";

    revision "2015-01-05" {
        description "Initial revision of messenger model";
    }

    grouping message {
        leaf mess-id {
            description "message Id";
            type string;
            mandatory true;
        }
        leaf text {
            description "message text";
            type string;
        }
        leaf message-source {
            description "message source";
            type string;
        }
        leaf message-dest {
            description "message dest";
            type string;
        }
    }

    container messenger {
        leaf id {
            type string;
            mandatory true;
        }
        leaf connected {
            description "indicate if the messenger service is connected";
            type boolean;
            default true;
            config false;
        }
        leaf last-message-datetime {
            type string;
        }
        list message {
            key mess-id;
            uses message;
        }
    }

    notification messenger-connection {
        description
          "Notify the messenger to be connected or disconnected.";
        leaf connected {
            type boolean;
        }
    }
}
